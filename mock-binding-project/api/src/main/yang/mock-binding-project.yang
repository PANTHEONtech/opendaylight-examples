module mock-binding-project {
    yang-version 1.1;
    namespace "urn:opendaylight:params:xml:ns:yang:mock-binding-project";
    prefix "mock-binding-project";

    revision "2018-05-17" { // TODO change revision to date of model creation
        description "Initial revision of mock-binding-project model";
    }
}
